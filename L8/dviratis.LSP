(defun c:dviratis()
  (setq ptaskas (getpoint "\n Iveskite piesinio apatinio kairiojo kampo koordinates (x,y):") )
  (command "osnap" "off" )
  (setq ptx (car ptaskas) )
  (setq pty (cadr ptaskas) )

  (setq ratas1 (list (+ ptx 20) (+ pty 20)))
  (setq ratas2 (list (+ (car ratas1) 50) (cadr ratas1)) )
  
  (setq taskas3 (list (+ (car ratas1) 15) (+(cadr ratas1)18)) )
  (setq taskas4 (list (+ (car ratas1) 20) (cadr ratas1)))
  (setq taskas5 (list (+ (car taskas3) 20) (+(cadr taskas3)5)))
  (setq taskas6 (list (- (car taskas3) 2) (+(cadr taskas3)3)))
  (setq taskas7 (list (+ (car taskas5) 0.5) (+(cadr taskas5)3)))
  (setq taskas8 (list (+ (car taskas7) 2) (+(cadr taskas7)0.5)))
  
  (setq pedalo1 (list (+ (car taskas4) 7) (-(cadr taskas4)2)))
  (setq pedalo2 (list (+ (car pedalo1) 0.8) (+(cadr pedalo1)0.8)))
  (setq pedalo3 (list (-(car pedalo1) 0.8) (-(cadr pedalo1)0.8)))
  
  (setq sedynes1 (list (+(car taskas6) 1.2) (+(cadr taskas6)1.2)))
  (setq sedynes2 (list (-(car taskas6) 1.2) (-(cadr taskas6)1.2)))
  (setq sedynes3 (list (-(car taskas6) 1.23) (-(cadr taskas6)1.25)))
  
  (setq taskas9 (list (car ratas1) (-(cadr ratas1)12.6)))
  (setq taskas10 (list (car ratas2) (-(cadr ratas2)12.6)))
  
  (command "COLOR" 249)
  (command "DONUT" 25 27 ratas1 "")
  (command "DONUT" 25 27 ratas2 "")
  (command "lweight" 0.5 "")
  (command "COLOR" 180)
  (command "LINE" ratas1 taskas3 "")
  (command "LINE" ratas1 taskas4 "")
  (command "LINE" taskas4 taskas3 "")
  (command "LINE" taskas3 taskas5 "")
  (command "LINE" taskas5 ratas2 "")
  (command "LINE" taskas5 taskas4 "")
  (command "LINE" taskas3 taskas6"")
  (command "LINE" taskas5 taskas7"")
  (command "LINE" taskas7 taskas8"")
  (command "COLOR" 249)
  (command "DONUT" 0 5 taskas4 "")
  (command "DONUT" 0 1 ratas1 "")
  (command "DONUT" 0 1 ratas2 "")
  (command "DONUT" 5 7 ratas1 "")
  (command "DONUT" 5 7 ratas2 "")
  (command "DONUT" 0 2 taskas8 "")
  (command "COLOR" 180)
  (command "LINE" taskas4 pedalo1"")
  (command "COLOR" 249)
  (command "LINE" pedalo1 pedalo2"")
  (command "LINE" pedalo1 pedalo3"")
  (command "ARC" sedynes1 sedynes2 sedynes3 "")
  (command "LINE" ratas1 taskas9"")
  
  (command "arraypolar" taskas9 "" ratas1 "i" 20 "" "")
  (command "LINE" ratas2 taskas10"")
  (command "arraypolar" taskas10 "" ratas2 "i" 20 "" "")
)
