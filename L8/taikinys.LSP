(defun C:taikinys()
  (setq taskas1 (getpoint "\n Nurodykite centra"))
  (command "lweight" 0.5)
  (command "circle" taskas1 30 "")
  (setq taskas2 (list (car taskas1) (-(cadr taskas1)50)))
  (setq taskas3 (list (car taskas1) (+(cadr taskas1)50)))
  (setq taskas4 (list (-(car taskas1)50) (cadr taskas1)))
  (setq taskas5 (list (+(car taskas1)50) (cadr taskas1)))

  (setq taskas22 (list (car taskas1) (-(cadr taskas1)3)))
  (setq taskas33 (list (car taskas1) (+(cadr taskas1)3)))
  (setq taskas44 (list (-(car taskas1)3) (cadr taskas1)))
  (setq taskas55 (list (+(car taskas1)3) (cadr taskas1)))
  (command "LINE" taskas22 taskas2  "")
  (command "LINE" taskas33 taskas3  "")
  (command "LINE" taskas44 taskas4  "")
  (command "LINE" taskas55 taskas5  "")
 )
